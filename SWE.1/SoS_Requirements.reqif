# SOS Requirements

# Specification: Failures
- Description: Failures

## REQ-4 (Failure)
- Syndrome: Safety component can write others component memory
- AbstractedTo -> SG-1

## REQ-5 (Failure)
- Syndrome: Safety component is not executed to completion
- AbstractedTo -> SG-2

## REQ-6 (Failure)
- Syndrome: OS shall not overwrite components data
- AbstractedTo -> SG-1

## REQ-1 (Failure)
- Syndrome: QM can write ASIL memory
- Counter Measure: asdfasf
- AbstractedTo -> SG-1

## REQ-3 (Failure)
- Syndrome: Safety component can write others component memory
- Location: TBD
- AbstractedTo -> SG-1

# Specification
- Description: Safety Goals

## SG-2 (SafetyGoal)
time  freedom of interference

## SG-1 (SafetyGoal)
space freedom of interference

# Specification
- Description: SoS Requirment Specification

## REQ-9 (Headline)
Safety OS - SOS - Requirment Specification

### REQ-10 (Information)
The Seooc is called Safety Operating System (SOS). it's a piece of software running in secure mode of the processor to allow safe execution of safety software components below a qm operating system without interference of it. The safety components are executed to completion according to a static schedule. The main idea is to exploit the secure domain as  a safety domain - as security has very similar requirements of safety when it comes to freedom of interference.

### REQ-24 (Headline)
Assumptions

#### REQ-13 (Assumption)
The CPU is expected to be ARMv8  using 64bit instructions only

#### REQ-14 (Assumption)
The CPU is expected to load SOS in a secure booted way, with QM quality.

#### REQ-15 (Assumption)
The CPU is expected to be at exception level 3 at the entry point of the SOS

#### REQ-16 (Assumption)
It is expected the system has an external window watchdog

#### REQ-18 (Assumption)
it's expected it is a safe action to stop execution in case of any failure. e.g. page fault, unexpected interrupt

#### REQ-19 (Assumption)
it's expected the watchdog is called by one of the safety components

#### REQ-20 (Assumption)
it's expected for a safety component the worst case execution time is known

#### REQ-21 (Assumption)
the system is expected to be schedulable or does not boot

#### REQ-22 (Assumption)
the SoC can protect secure memory from non secure access

#### REQ-23 (Assumption)
it is expected the memory is statically allocated to safe and non safe software domains.

#### REQ-72 (Assumption)
communication happens through lockless queues between QM and safety component, where the state and output is stored at least twice. with CRC support the last correct dataset shall be used

### REQ-25 (Headline)
Requirements

#### REQ-26 (Requirment)
the SOS shall not allow a safety component's memory to be overwritten by any other component

#### REQ-44 (Requirment)
SOS shall program the interrupt controller so that the timer interrupt is periodically executed with highest priority

##### REQ-45 (Requirment)
The smallest time slice shall be 10ms

#### REQ-42 (Requirment)
SOS shall program the MMU and System Memory protection unit

##### REQ-43 (Requirment)
SOS shall use physical memory addresses only

#### REQ-37 (Requirment)
SOS shall be statically linked with the safety components

##### REQ-38 (Requirment)
SOS shall reserve the remaining memory for the QM Guest OS

##### REQ-40 (Requirment)
SOS shall execute the QM Guest OS if no SafetyComponent is runable

###### REQ-52 (Requirment)
SOS shall execute the QM guest on EL2 (or EL1 as an option)

###### REQ-53 (Requirment)
SOS shall contain the QM guest program loader as part of it's image

###### REQ-54 (Requirment)
guest program loader has to have the entry point at the beginning of the image

###### REQ-55 (Requirment)
guest QM shall accept in R0 the memory location to be used

###### REQ-56 (Requirment)
guest QM shall accept in R1 the memory size  to be used

##### REQ-41 (Requirment)
Guest OS shall have a defined output region writable by the Guest OS

#### REQ-27 (Requirment)
the SOS shall schedule each safety component at the expected periodicity

##### REQ-28 (Requirment)
as Safety Component shall have a PERIOD

###### REQ-31 (Requirment)
safety component shall define periodic function

###### REQ-32 (Requirment)
safety component shall define a init function

###### REQ-48 (Requirment)
SOS shall call the init function of all safety components until the init function returns 0

###### REQ-58 (Requirment)
components shall be able to update their Periodicity and WCET at runtime

###### REQ-59 (Requirment)
SOS shall keep track of the worst WCET of each component

##### REQ-29 (Requirment)
a Safety Component shall have a WCET (Worst case execution time)

##### REQ-30 (Requirment)
the SOS shall schedule each safety component at the expected periodicity

##### REQ-46 (Requirment)
WCET and PRIODICITY shall be given in 0.1 ms

##### REQ-51 (Requirment)
SOS shall provide a 24 MB stack space with guard page

#### REQ-33 (Requirment)
safety component shall statically allocate the memory

##### REQ-34 (Requirment)
safety compoent shall have a defined private memory not readable by others

##### REQ-35 (Requirment)
safety component shall have a defined output memory readable by others

##### REQ-36 (Requirment)
safety component may own memory sections for R/W

#### REQ-47 (Requirment)
SOS shall initialize all memory

#### REQ-49 (Requirment)
SOS shall not use exception (misra)

#### REQ-50 (Requirment)
SOS shall leave each function from one location, except main

#### REQ-57 (Requirment)
in case of unexpected interrupt, shall increment the tripple error counter and execute from the next .text segment the timerhandler

#### REQ-60 (Requirment)
SOS shall use all but the first CPU core in a multi core systems

#### REQ-61 (Requirment)
SOS, safety components and QM shall have list of writable memory region

##### REQ-62 (Requirment)
each memory region is owned by only one component

#### REQ-63 (Requirment)
SOS shall not use dynamic memory (new,allocate)

#### REQ-64 (Requirment)
SOS shall support up to NUM_SAFTYCOMPONENTS  safety components (limits the array size)

##### REQ-67 (Requirment)
if more than supported (configured) safety component are linked the system shall not boot.

#### REQ-65 (Requirment)
the usage of plain pointer is forbidden  (this means static located array are allowed)

#### REQ-66 (Requirment)
all data elements which are read only shall be private with inline access function. (private data shall be private)

#### REQ-68 (Requirment)
SOS shall come with a simulation environment where the code is executed in Emulator  (cpu model of ARM) which is killed after 20s, in this 20s the test code has to execute and print expected or unexpected output. each test case has to be reported how many expected messages are printed. a test case is failed if a unexpected message is printed.

#### REQ-69 (Requirment)
It has to be possible to retreive the branch and function coverage from test cases

#### REQ-70 (Requirment)
static data should exist twice so that a CRC check can determine which one is write and can be corrected.

#### REQ-71 (Requirment)
the timer shall be reprogrammed after each expire

#### REQ-73 (Requirment)
all code has to be position independent

##### REQ-74 (Requirment)
All code has to exist twice and shall be executed alternativly

#### REQ-75 (Requirment)
the image shall have a CRC which is checked during startup

##### REQ-76 (Requirment)
.text section shall have a CRC and be existing twice,  shall be checked for 200 bytes per Interrupt tick for correctness

#### REQ-77 (Requirment)
each core shall use it's own stack

#### REQ-79 (Requirment)
__cxa_pure_virtual shall be defined as an endless loop, it may produce a debug message that a pure virtual fuction is called

#### REQ-80 (Requirment)
SOS shall not support runtime type information -fno-rtti

#### REQ-81 (Requirment)
SOS shall disallow exceptions

#### REQ-82 (Requirment)
SOS shall define memset

## REQ-39 (Requirment)

## REQ-78 (Requirment)
